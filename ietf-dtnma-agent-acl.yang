module ietf-dtnma-agent-acl {
  yang-version 1.1;
  namespace "ari://ietf-dtnma-agent-acl";
  prefix acl;
  amm:enum 2;

  import ietf-amm {
    prefix amm;
  }
  import ietf-dtnma-agent {
    prefix da;
  }

  organization
    "IETF Delay Tolerant Networking (DTN) Working Group";
  contact
    "WG Web: <http://tools.ietf.org/wg/dtn/>
     WG List: <mailto:dtn@ietf.org>

     Editor: Brian Sipos
             <mailto:brian.sipos+ietf@gmail.com>";
  description
    "This module implements the DTN Management Architecture (DTNMA)
     Agent Access Control List (ACL) functionality.";
  reference
    "draft-ietf-dtn-adm-yang";

  revision 2024-07-03 {
    description
      "Updated for latest ADM document.";
    reference
      "draft-ietf-dtn-adm-yang";
  }
  revision 2023-12-12 {
    description
      "Initial version for latest AMM document";
    reference
      "draft-birrane-dtn-adm";
  }
  amm:typedef tag {
    amm:type "./TYPEDEF/permissions";
    description
      "Datatype for access control list tags";
  }
  amm:typedef permissions {
    amm:type "/ARITYPE/BYTE" {
      amm:int-labels {
        bit tag-read {
          position 0;
          description
            "Permission bit for Read";
        }
        bit tag-write {
          position 1;
          description
            "Permission bit for Write";
        }
        bit tag-execute {
          position 2;
          description
            "Permission bit for Execute/Evaluate";
        }
      }
    }
  }
  amm:typedef entry-id {
    amm:type "/ARITYPE/UVAST";
    description
      "The identifier for an entry in any access control table.";
  }
  amm:typedef optional-entry-id {
    amm:union {
      amm:type "./TYPEDEF/entry-id";
      amm:type "/ARITYPE/null";
    }
    description
      "An optional entry identifier (or a null value).";
  }
  amm:typedef result {
    amm:type "/ARITYPE/INT" {
      amm:int-labels {
        enum success {
          value 0;
          description
            "Execution was successful";
        }
        enum error-generic {
          value 1;
          description
            "Generic execution failure";
        }
        enum error-permission-denied {
          value 2;
          description
            "Manager does not have permission";
        }
      }
    }
  }

  // Default access permission
  amm:var default-access {
    amm:enum 1;
    amm:type "./TYPEDEF/tag";
    description
      "The default permission for any object if no specific access are
       present in the ./EDD/access-list table.";
  }

  // Access control table and modifier controls
  amm:edd access-list {
    amm:enum 2;
    amm:tblt {
      amm:key "id";
      amm:column id {
        amm:type "./TYPEDEF/entry-id";
      }
      amm:column group {
        amm:type "./TYPEDEF/optional-entry-id";
        description
          "A cross-reference to the group getting access, or null to match all groups.";
      }
      amm:column object-pattern {
        amm:type "/ARITYPE/TEXTSTR";
        description
          "A pattern for objects being accessed, which may match all objects.";
      }
      amm:column tag {
        amm:type "./TYPEDEF/tag";
        description
          "A pattern for objects being accessed, which may match all objects.";
      }
    }
    description
      "List the current group--object access.";
  }
  amm:ctrl ensure-access {
    amm:enum 3;
    amm:parameter group {
      amm:type "./TYPEDEF/optional-entry-id";
      description
        "Identify the group being assigned the permission";
    }
    amm:parameter object-pattern {
      amm:type "/ARITYPE/TEXTSTR";
      description
        "ARI pattern to determine which objects shall be assigned the permission";
    }
    amm:parameter tag {
      amm:type "./TYPEDEF/tag";
      amm:default "0";
      description
        "Permission tag value to set";
    }
    amm:result error-code {
      amm:type "./TYPEDEF/result";
      description
        "If non-zero, an indicator of an error.";
    }
    description
      "Ensures that an access control permission is set for the given group and ARI pattern.";
  }
  amm:ctrl discard-access {
    amm:enum 4;
    amm:parameter group {
      amm:type "./TYPEDEF/optional-entry-id";
      description
        "Identify the group";
    }
    amm:parameter object-pattern {
      amm:type "/ARITYPE/TEXTSTR";
      description
        "ARI pattern";
    }
    amm:result error-code {
      amm:type "./TYPEDEF/result";
      description
        "If non-zero, an indicator of an error.";
    }
    description
      "Discard any permissions for the given group and ARI pattern.";
  }

  //
  // Group management
  //
  amm:typedef transport-endpoint-pattern {
    amm:type "/ARITYPE/IDENT" {
      amm:base "//ietf-dtnma-agent/IDENT/transport-endpoint-pattern";
    }
  }
  amm:edd current-group-id {
    amm:enum 3;
    amm:type "./TYPEDEF/entry-id";
    description
      "Get the group ID for the current execution context, which may be
       the implicit Agent group ID zero.";
  }
  amm:edd group-list {
    amm:enum 4;
    amm:tblt {
      amm:key "id";
      amm:column id {
        amm:type "./TYPEDEF/entry-id";
        description
          "The unique identifier for a group.
           The agent itself has implicit group ID zero.";
      }
      amm:column name {
        amm:type "/ARITYPE/TEXTSTR";
        description
          "The human-friendly name of the group.";
      }
      amm:column members {
        amm:ulist {
          amm:type "./TYPEDEF/transport-endpoint-pattern";
        }
        description
          "The list of members of the group, identified by matching transport endpoint.";
      }
    }
    description
      "Get the defined access control groups.";
  }
  amm:ctrl ensure-group {
    amm:enum 5;
    amm:parameter id {
      amm:type "./TYPEDEF/entry-id";
      description
        "Uniquely identify the group";
    }
    amm:parameter name {
      amm:type "/ARITYPE/TEXTSTR";
      description
        "Name of the group";
    }
    amm:result error-code {
      amm:type "./TYPEDEF/result";
      description
        "If non-zero, an indicator of an error.";
    }
    description
      "Ensure that after the control completes a group exists with the given information";
  }
  amm:ctrl ensure-group-members {
    amm:enum 7;
    amm:parameter id {
      amm:type "./TYPEDEF/entry-id";
      description
        "Uniquely identify the group";
    }
    amm:parameter members {
      amm:ulist {
        amm:type "./TYPEDEF/transport-endpoint-pattern";
      }
    }
    amm:result error-code {
      amm:type "./TYPEDEF/result";
      description
        "If non-zero, an indicator of an error.";
    }
    description
      "Ensure that the membership of a group has a specific set of endpoint patterns.";
  }
  amm:ctrl discard-group {
    amm:enum 6;
    amm:parameter group {
      amm:type "./TYPEDEF/entry-id";
      description
        "Uniquely identify the group";
    }
    amm:result error-code {
      amm:type "./TYPEDEF/result";
      description
        "If non-zero, an indicator of an error.";
    }
    description
      "Discard any group with the given ID.";
  }
}
