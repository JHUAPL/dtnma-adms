module ietf-amm {
  yang-version 1.1;
  namespace "ari://ietf-amm/";
  prefix amm;

  organization
    "IETF Delay Tolerant Networking (DTN) Working Group";
  contact
    "WG Web: <http://tools.ietf.org/wg/dtn/>
     WG List: <mailto:dtn@ietf.org>

     Editor: Brian Sipos
             <mailto:brian.sipos+ietf@gmail.com>";
  description
    "This module defines the DTN Management Architecture (DTNMA)
     Application Management Model (AMM) extensions within YANG.
     It also defines the base IDENT and TYPEDEF objects for the AMM.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2024-07-03 {
    description
      "Updated for latest ADM document.";
    reference
      "draft-ietf-dtn-adm-yang";
  }
  revision 2023-06-08 {
    description
      "Updated for latest AMM contents.";
    reference
      "draft-birrane-dtn-adm";
  }
  revision 2016-04-01 {
    description
      "Updated to fix typos.";
    reference
      "draft-bsipos-dtn-amp-yang";
  }
  revision 2016-03-14 {
    description
      "Initial draft release.";
    reference
      "draft-bsipos-dtn-amp-yang";
  }

  /*
   * This section contains extensions for common behavior of AMM objects.
   */

  extension enum {
    argument value;
    description
      "An enumeration identifies an object within a namespace.
       The argument to this statement is the integer value.";
  }

  extension parameter {
    argument name;
    description
      "The schema for a formal parameter of an object.
       Order of parameters is significant within this statement.";
  }

  extension default {
    argument value;
    description
      "The literal value default for a parameter or result.
       The argument is the text form of the ARI";
  }

  extension init-value {
    argument value;
    description
      "The literal value of a CONST object,
       initial state for a VAR object.
       The argument is the text form of the ARI";
  }

  extension init-expr {
    argument expr;
    description
      "An expression evaluated to initialize a VAR object.
       The argument is the text form of the EXPR AC";
  }

  /*
   * This section contains extensions for AMM object definitions.
   */

  extension typedef {
    argument name;
    description
      "Definition of a TYPEDEF within an ADM.
       The argument to this statement is the object name.
       One of the type use substatements must be present.";
  }

  extension ident {
    argument name;
    description
      "Definition of an IDENT within an ADM.
       The argument to this statement is the object name.
       An 'base' substatement must be present.";
  }

  extension base {
    argument name;
    description
      "The argument is the base of an IDENT object.";
  }

  extension const {
    argument name;
    description
      "Definition of a CONST within an ADM.
       The argument to this statement is the object name.
       An 'init-value' substatement must be present.";
  }

  extension ctrl {
    argument name;
    description
      "Definition of a CTRL within an ADM.
       The argument to this statement is the object name.";
  }

  extension result {
    argument name;
    description
      "A result value reported as a response to a control.
       The substatement is the result type.
       Each CTRL can have a single optional result.";
  }

  extension edd {
    argument name;
    description
      "Definition of an EDD within an ADM.
       The argument to this statement is the object name.";
  }

  extension oper {
    argument name;
    description
      "Definition of an OPER within an ADM.
       The argument to this statement is the object name.";
  }

  extension operand {
    argument name;
    description
      "An individual operand taken from the expression stack
       during evaluation of the OPER.
       Each substatement is an operand as a leaf (ARI).
       Order of operands is significant within an object definition.";
  }

  extension var {
    argument name;
    description
      "Definition of a VAR within an ADM.
       The argument to this statement is the object name.";
  }

  /*
   * This section contains extensions for defining semantic type instances.
   */

  extension type {
    argument name;
    description
      "A reference to a built-in type or prefix-qualified typedef.";
  }

  extension display-hint {
    argument ident;
    description
      "Reference an IDENT object which indicates how a value should be
       displayed for human consumption.
       The base of the IDENT SHALL be the ./IDENT/display-hint object.";
  }

  extension int-labels {
    description
      "Type narrowing for an integer to label enum values or bit positions.";
  }

  extension cddl {
    argument text;
    description
      "Type narrowing for a CBOR item in the form of CDDL syntax.
       The argument to this statement is the actual CDDL text.";
  }

  extension ulist {
    description
      "Type for an AC containing a list of uniform-typed values.";
  }

  extension dlist {
    description
      "Type for an AC containing a list of diverse-typed sequences.";
  }

  extension seq {
    description
      "A sequence of uniform-typed values within a 'dlist'.";
  }

  extension umap {
    description
      "Type for an AM containing a set of uniform-typed key-value pairs.";
  }

  extension keys {
    description
      "The type restriction for 'umap' keys.";
  }

  extension values {
    description
      "The type restriction for 'umap' values.";
  }

  extension tblt {
    description
      "Type for a table of values with a column schema.";
  }

  extension column {
    argument name;
    description
      "An individual column within a 'tblt' definition.";
  }

  extension key {
    argument columns;
    description
      "Names of columns composing the row key, separated by spaces,
       within a 'tblt' definition.";
  }

  extension unique {
    argument columns;
    description
      "Names of columns composing a uniqueness constraint, separated by
       spaces, within a 'tblt' definition.";
  }

  extension union {
    description
      "Type for a union of other types.";
  }

  amm:enum 0;

  // Base IDENT objects
  amm:ident display-hint {
    amm:enum 0;
    description
      "The base IDENT for objects usable as arguments for the
       'amm:display-hint' extension.
       This object itself provides no display hint purpose.";
  }
  amm:ident semtype {
    amm:enum 1;
    description
      "The base IDENT for semantic type introspection.
       This object itself provides no type information.";
  }

  // Semantic-type leaf IDENT objects
  amm:ident semtype-use {
    amm:enum 2;
    description
      "A named type use and possibly augment.";
    amm:base "./IDENT/semtype";
    amm:parameter name {
      description
        "A built-in ARITYPE or reference to TYPEDEF object being used.";
      amm:type "./TYPEDEF/type-ref";
    }
    // FIXME include constraints and annotations also?
  }
  amm:ident semtype-ulist {
    amm:enum 3;
    description
      "A uniformly-typed list within an AC.";
    amm:base "./IDENT/semtype";
    amm:parameter item-type {
      description
        "The semantic type for all items.";
      amm:type "./TYPEDEF/semtype";
    }
    amm:parameter min-elements {
      description
        "The smallest valid item count for the AC.";
      amm:default "null";
      amm:union {
        amm:type "/ARITYPE/uvast";
        amm:type "/ARITYPE/null";
      }
    }
    amm:parameter max-elements {
      description
        "The largest valid item count for the AC.";
      amm:default "null";
      amm:union {
        amm:type "/ARITYPE/uvast";
        amm:type "/ARITYPE/null";
      }
    }
  }
  amm:ident semtype-dlist {
    amm:enum 4;
    description
      "A diverse-typed list within an AC.";
    amm:base "./IDENT/semtype";
    amm:parameter item-types {
      description
        "The list of semantic type for each item in sequence within the list.
         The list itself is encoded as an AC in this parameter.";
      amm:ulist {
        amm:type "./TYPEDEF/semtype";
      }
    }
  }
  amm:ident semtype-umap {
    amm:enum 5;
    description
      "A uniformly-typed map within an AM.";
    amm:base "./IDENT/semtype";
    amm:parameter key-type {
      description
        "The semantic type for each key.";
      amm:type "./TYPEDEF/semtype";
    }
    amm:parameter value-type {
      description
        "The semantic type for each value.";
      amm:type "./TYPEDEF/semtype";
    }
  }
  amm:ident semtype-tblt {
    amm:enum 6;
    description
      "A parameterized table template for data within a TBL.";
    amm:base "./IDENT/semtype";
    amm:parameter columns {
      description
        "The list of column definitions.
         Each column SHALL have a unique name.";
      amm:type "/ARITYPE/ident" {
        amm:base "./IDENT/semtype-tblt-col";
      }
    }
    amm:parameter min-elements {
      description
        "The smallest valid row count for the TBL.";
      amm:default "null";
      amm:union {
        amm:type "/ARITYPE/uvast";
        amm:type "/ARITYPE/null";
      }
    }
    amm:parameter max-elements {
      description
        "The largest valid row count for the TBL.";
      amm:default "null";
      amm:union {
        amm:type "/ARITYPE/uvast";
        amm:type "/ARITYPE/null";
      }
    }
    amm:parameter key {
      description
        "The primary key column names in this table, as comma-separated labels.";
      amm:default "null";
      amm:union {
        amm:type "/ARITYPE/textstr";
        amm:type "/ARITYPE/null";
      }
    }
    amm:parameter unique {
      description
        "The set of unique column names in this table, as comma-separated labels.
         The set itself is encoded as an AC in this parameter.";
      amm:default "/AC/()";
      amm:ulist {
        amm:type "/ARITYPE/textstr";
      }
    }
  }
  amm:ident semtype-tblt-col {
    amm:enum 7;
    description
      "A parameterized table column within a template.
       This object does not have a base as it is not substitutable.";
    amm:parameter name {
      description
        "The name of this column.
         Each name SHALL be restricted to valid label text.";
      amm:type "/ARITYPE/label";
    }
    amm:parameter datatype {
      description
        "The semantic type for values in this column.";
      amm:type "./TYPEDEF/semtype";
    }
  }
  amm:ident semtype-union {
    amm:enum 8;
    description
      "A list of alternative type choices.";
    amm:base "./IDENT/semtype";
    amm:parameter choices {
      description
        "The semantic type for each choice.
         The list itself is encoded as an AC in this parameter.";
      amm:ulist {
        amm:type "./TYPEDEF/semtype";
      }
    }
  }
  amm:ident semtype-seq {
    amm:enum 9;
    description
      "A sequence of similarly-typed items as a sub-sequence of an AC.
       This is only usable in specific contexts, such as within a
       ./IDENT/semtype-dlist parameter.";
    amm:base "./IDENT/semtype";
    amm:parameter item-type {
      description
        "The semantic type for all items in the sequence.";
      amm:type "./TYPEDEF/semtype";
    }
    amm:parameter min-elements {
      description
        "The smallest valid item count for the sequence.";
      amm:default "null";
      amm:union {
        amm:type "/ARITYPE/uvast";
        amm:type "/ARITYPE/null";
      }
    }
    amm:parameter max-elements {
      description
        "The largest valid item count for the sequence.";
      amm:default "null";
      amm:union {
        amm:type "/ARITYPE/uvast";
        amm:type "/ARITYPE/null";
      }
    }
  }

  // Named type unions
  amm:typedef type-ref {
    amm:enum 0;
    description
      "Reference to either a built-in type or a TYPEDEF object.";
    amm:union {
      amm:type "/ARITYPE/aritype";
      amm:type "/ARITYPE/typedef";
    }
  }
  amm:typedef semtype {
    amm:enum 25;
    description
      "A parameterized reference to a semantic type object.
       This is used for introspection of AMM objects.";
    amm:type "/ARITYPE/ident" {
      amm:base "./IDENT/semtype";
    }
  }
  amm:typedef integer {
    amm:enum 1;
    description
      "Any type which represents a discrete integer
       This union order prefers smaller range and signed types.";
    amm:union {
      amm:type "/ARITYPE/byte";
      amm:type "/ARITYPE/int";
      amm:type "/ARITYPE/uint";
      amm:type "/ARITYPE/vast";
      amm:type "/ARITYPE/uvast";
    }
  }
  amm:typedef float {
    amm:enum 2;
    description
      "Any type which represents a floating point number.";
    amm:union {
      amm:type "/ARITYPE/real32";
      amm:type "/ARITYPE/real64";
    }
  }
  amm:typedef numeric {
    amm:enum 3;
    description
      "Any type which can be used with numeric expressions.";
    amm:union {
      amm:type "./TYPEDEF/integer";
      amm:type "./TYPEDEF/float";
    }
  }
  amm:typedef primitive {
    amm:enum 4;
    description
      "Any primitive type.";
    amm:union {
      amm:type "/ARITYPE/null";
      amm:type "/ARITYPE/bool";
      amm:type "./TYPEDEF/numeric";
      amm:type "/ARITYPE/textstr";
      amm:type "/ARITYPE/bytestr";
    }
  }
  amm:typedef time {
    amm:enum 5;
    description
      "Any type which can be used with time expressions.";
    amm:union {
      amm:type "/ARITYPE/TP";
      amm:type "/ARITYPE/TD";
    }
  }
  amm:typedef simple {
    amm:enum 6;
    description
      "Any type which contains a single literal value (not nested).";
    amm:union {
      amm:type "./TYPEDEF/PRIMITIVE";
      amm:type "./TYPEDEF/TIME";
    }
  }
  amm:typedef nested {
    amm:enum 7;
    description
      "A literal type which contains other ARI values.";
    amm:union {
      amm:type "/ARITYPE/AC";
      amm:type "/ARITYPE/AM";
      amm:type "/ARITYPE/TBL";
    }
  }
  amm:typedef any {
    amm:enum 8;
    description
      "Any value representable by an ARI.";
    // These type names are built-in
    amm:union {
      amm:type "/ARITYPE/literal";
      amm:type "/ARITYPE/object";
    }
  }
  amm:typedef value-obj {
    amm:enum 9;
    description
      "A reference to an object which can produce a value.";
    amm:union {
      amm:type "/ARITYPE/const";
      amm:type "/ARITYPE/edd";
      amm:type "/ARITYPE/var";
    }
  }
  amm:typedef nonce {
    amm:enum 10;
    description
      "This type union is used to correlate Agent-Manager messages.";
    amm:union {
      amm:type "/ARITYPE/bytestr";
      amm:type "/ARITYPE/uvast";
      amm:type "/ARITYPE/null";
    }
  }

  // operational semantic types
  amm:typedef counter32 {
    amm:enum 11;
    description
      "A 32-bit counter with an arbitrary initial value that only increments.
       When the value reaches the upper range it wraps around to zero.
       At least two samples of this value need to be compared over time.";
    amm:type "/ARITYPE/uint";
  }
  amm:typedef counter64 {
    amm:enum 12;
    description
      "A 64-bit counter with an arbitrary initial value that only increments.
       When the value reaches the upper range it wraps around to zero.
       At least two samples of this value need to be compared over time.";
    amm:type "/ARITYPE/uvast";
  }
  amm:typedef gauge32 {
    amm:enum 13;
    description
      "A 32-bit value sampling some quantized measurement.
       The value can increase or decrease arbitrarily over time.";
    amm:type "/ARITYPE/int";
  }
  amm:typedef gauge64 {
    amm:enum 14;
    description
      "A 64-bit value sampling some quantized measurement.
       The value can increase or decrease arbitrarily over time.";
    amm:type "/ARITYPE/vast";
  }
  amm:typedef timestamp {
    amm:enum 15;
    description
      "A time point representing the system clock at which a specific
       occurrence happened.
       The specific occurrence must be defined in the description
       of any node defined using this type.";
    amm:type "/ARITYPE/tp";
  }

  // Restrictions on AC item types for Evaluation and EXPR
  amm:typedef eval-tgt {
    amm:enum 16;
    description
      "A value which can be the target of an evaluation.";
    amm:union {
      amm:type "./TYPEDEF/simple"; // special case of literal value result
      amm:type "./TYPEDEF/value-obj"; // produces an eval-tgt
      amm:type "./TYPEDEF/expr";
    }
  }
  amm:typedef expr-item {
    amm:enum 17;
    description
      "Each item of an EXPR list.";
    amm:union {
      amm:type "./TYPEDEF/simple";
      amm:type "./TYPEDEF/value-obj"; // produces an eval-tgt
      amm:type "./TYPEDEF/type-ref"; // treated as unary operator
      amm:type "/ARITYPE/label"; // substitutable label
      amm:type "/ARITYPE/oper";
    }
  }
  amm:typedef expr {
    amm:enum 18;
    description
      "The contents of an EXPR container.";
    amm:ulist {
      amm:type "./TYPEDEF/expr-item";
    }
  }

  // Restrictions on AC item types for Execution and MAC
  amm:typedef exec-tgt {
    amm:enum 19;
    description
      "A value which can be the target of an execution.";
    amm:union {
      amm:type "./TYPEDEF/exec-item";
      amm:type "./TYPEDEF/mac";
    }
  }
  amm:typedef exec-item {
    amm:enum 20;
    description
      "A reference to an object which can be executed.
       The value-object must be typed to contain an exec-tgt.";
    amm:union {
      amm:type "/ARITYPE/ctrl";
      amm:type "./TYPEDEF/value-obj"; // produces an exec-tgt
    }
  }
  amm:typedef mac {
    amm:enum 21;
    description
      "The contents of a MAC container are an ordered list of
       executable values.";
    amm:ulist {
      amm:type "./TYPEDEF/exec-item";
    }
  }

  // Restrictions on AC item types for Reporting and RPTT
  amm:typedef rpt-tgt {
    amm:enum 22;
    description
      "A value which can be the target of reporting.";
    amm:union {
      amm:type "./TYPEDEF/value-obj"; // produces an RPTT
      amm:type "./TYPEDEF/rptt";
    }
  }
  amm:typedef rptt-item {
    amm:enum 23;
    description
      "Each item of a RPTT.
       Each item references a value-producing object or contains an
       expression to be evaluated.";
    amm:union {
      amm:type "./TYPEDEF/value-obj";
      amm:type "./TYPEDEF/expr";
    }
  }
  amm:typedef rptt {
    amm:enum 24;
    description
      "The contents of a report template, encoded as the sequence of items.";
    amm:ulist {
      amm:type "./TYPEDEF/rptt-item";
    }
  }
}
